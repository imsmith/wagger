module notes-service-mcp {
  yang-version 1.1;
  namespace "urn:wagger:notes-service:mcp";
  prefix notes-service;
  import mcp {
    prefix mcp;
    revision-date 2025-06-18;
  }
  revision YYYY-MM-DD {
    description "Generated by wagger.";
  }
  container tools {
    description "Declared MCP tools.";
    list tool {
      key "name";
      leaf name {
        type string;
        default "create_note";
      }
      uses mcp:tool-definition;
    }
    list tool {
      key "name";
      leaf name {
        type string;
        default "search_notes";
      }
      uses mcp:tool-definition;
    }
  }
  container resources {
    description "Declared MCP resources.";
    list resource {
      key "uri-template";
      leaf uri-template {
        type string;
        default "notes://{id}";
      }
      uses mcp:resource-definition;
    }
    list resource {
      key "uri-template";
      leaf uri-template {
        type string;
        default "config://";
      }
      uses mcp:resource-definition;
    }
  }
  container prompts {
    description "Declared MCP prompts.";
    list prompt {
      key "name";
      leaf name {
        type string;
        default "summarize";
      }
      uses mcp:prompt-definition;
    }
  }
}
