module demo-mcp {
  yang-version 1.1;
  namespace "urn:wagger:demo:mcp";
  prefix demo;
  import mcp {
    prefix mcp;
    revision-date 2025-06-18;
  }
  revision YYYY-MM-DD {
    description "Generated by wagger.";
  }
  container tools {
    description "Declared MCP tools.";
  }
  container resources {
    description "Declared MCP resources.";
  }
  container prompts {
    description "Declared MCP prompts.";
  }
}
