module wagger-gcp-armor {
  namespace "urn:wagger:gcp-armor";
  prefix wga;

  organization "Wagger Project";
  description "Data model for GCP Cloud Armor security policy configuration.";

  revision 2026-05-03 {
    description "Add allow-ip-ranges and allow-regions for posture-driven allow rules.
                 Cloud Armor role reframed: defense-in-depth behind URL Map.
                 (method, path) allowlisting moved to wagger-gcp-urlmap.yang.";
  }

  revision 2026-04-13 {
    description "Initial revision.";
  }

  container gcp-armor-config {
    description "Top-level GCP Cloud Armor security policy configuration.";

    leaf policy-name {
      type string;
      mandatory true;
      description "Name of the Cloud Armor security policy.";
    }

    leaf description {
      type string;
      description "Human-readable description of the security policy.";
    }

    leaf generated-at {
      type string;
      description "ISO 8601 timestamp of generation.";
    }

    leaf-list allow-ip-ranges {
      type string;
      description "Optional list of CIDR strings to restrict inbound traffic by IP.
                   When declared, Cloud Armor emits a versioned-expr allow rule
                   admitting only these source ranges. When absent or empty, all
                   source IPs are permitted (permissive allow, defense-in-depth
                   behind the URL Map). Example: '10.0.0.0/8', '203.0.113.0/24'.";
    }

    leaf-list allow-regions {
      type string;
      description "Optional list of ISO 3166-1 alpha-2 region codes to restrict
                   inbound traffic by geography. When declared, Cloud Armor emits
                   a CEL allow rule using origin.region_code. When absent or empty,
                   no geographic restriction is applied. Example: 'US', 'GB', 'CA'.
                   Can be combined with allow-ip-ranges for an AND match.";
    }

    list rules {
      key "priority";
      description "Security policy rules in priority order.";

      leaf priority {
        type uint32;
        mandatory true;
        description "Rule evaluation priority (lower = higher priority, 2147483647 = default).";
      }

      leaf description {
        type string;
        description "Human-readable description of this rule.";
      }

      leaf action {
        type enumeration {
          enum "allow";
          enum "deny(403)";
          enum "deny(429)";
          enum "rate_based_ban";
        }
        mandatory true;
        description "Action to take when the rule matches.";
      }

      leaf cel-expression {
        type string;
        description "CEL expression for this rule (used in match.expr).";
      }

      leaf match-type {
        type enumeration {
          enum "expr";
          enum "versioned-expr";
        }
        mandatory true;
        description "Type of match condition: CEL expression or versioned expression.";
      }

      leaf-list src-ip-ranges {
        type string;
        description "Source IP ranges for versioned-expr rules. Use ['*'] for all sources.
                     For posture allow rules, contains the declared allow-ip-ranges or ['*']
                     when no IP posture is configured.";
      }

      container rate-limit-options {
        description "Rate limiting options for rate_based_ban rules.";

        leaf conform-action {
          type string;
          mandatory true;
          description "Action for requests within the rate limit (e.g., 'allow').";
        }

        leaf exceed-action {
          type string;
          mandatory true;
          description "Action for requests exceeding the rate limit (e.g., 'deny(429)').";
        }

        leaf rate-limit-count {
          type uint32;
          mandatory true;
          description "Maximum request count within the interval.";
        }

        leaf rate-limit-interval-sec {
          type uint32;
          mandatory true;
          description "Interval in seconds for the rate limit window.";
        }
      }
    }
  }
}
