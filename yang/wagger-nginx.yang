module wagger-nginx {
  namespace "urn:wagger:nginx";
  prefix wn;

  organization "Wagger Project";
  description "Data model for nginx WAF-style allowlist configuration.";

  revision 2026-04-13 {
    description "Initial revision.";
  }

  container nginx-config {
    description "Top-level nginx WAF configuration.";

    leaf config-name {
      type string;
      mandatory true;
      description "Name prefix for generated config elements.";
    }

    leaf generated-at {
      type string;
      description "ISO 8601 timestamp of generation.";
    }

    container path-map {
      description "Map directive entries for path validation.";

      leaf default-value {
        type string;
        mandatory true;
        description "Default map value for unmatched paths.";
      }

      list entries {
        key "pattern";
        description "Map entries matching valid paths.";

        leaf pattern {
          type string;
          mandatory true;
          description "Regex or exact path pattern.";
        }

        leaf value {
          type string;
          mandatory true;
          description "Map value when pattern matches.";
        }
      }
    }

    list locations {
      key "path";
      description "Location blocks with method and rate limit configuration.";

      leaf path {
        type string;
        mandatory true;
        description "Location match pattern.";
      }

      leaf match-type {
        type enumeration {
          enum "exact";
          enum "prefix";
          enum "regex";
        }
        mandatory true;
        description "Nginx location match type.";
      }

      leaf-list allowed-methods {
        type string;
        description "HTTP methods allowed at this location.";
      }

      container rate-limit {
        description "Rate limiting configuration for this location.";

        leaf zone-name {
          type string;
          mandatory true;
          description "Nginx limit_req zone name.";
        }

        leaf burst {
          type uint32;
          mandatory true;
          description "Burst size for limit_req.";
        }
      }

      leaf upstream {
        type string;
        description "Proxy pass target.";
      }
    }
  }
}
