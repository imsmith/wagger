module wagger-zap {
  namespace "urn:wagger:zap";
  prefix wz;

  organization "Wagger Project";
  description "Data model for OWASP ZAP automation framework test plans.";

  revision 2026-04-14 {
    description "Initial revision.";
  }

  container zap-config {
    description "Top-level ZAP automation plan configuration.";

    leaf config-name {
      type string;
      mandatory true;
      description "Identifier for this test plan.";
    }

    leaf target-url {
      type string;
      mandatory true;
      description "Base URL of the deployed application under test.";
    }

    leaf generated-at {
      type string;
      description "ISO 8601 timestamp of generation.";
    }

    list positive-tests {
      key "url method";
      description "Requests expected to be allowed (non-403).";

      leaf url {
        type string;
        mandatory true;
        description "Full request URL.";
      }

      leaf method {
        type string;
        mandatory true;
        description "HTTP method.";
      }

      leaf description {
        type string;
        description "Human-readable test description.";
      }
    }

    list negative-method-tests {
      key "url method";
      description "Requests expected to be blocked (403) due to disallowed method.";

      leaf url {
        type string;
        mandatory true;
        description "Full request URL.";
      }

      leaf method {
        type string;
        mandatory true;
        description "HTTP method expected to be blocked.";
      }

      leaf description {
        type string;
        description "Human-readable test description.";
      }
    }

    list negative-path-tests {
      key "url method";
      description "Requests to undeclared paths expected to be blocked (403).";

      leaf url {
        type string;
        mandatory true;
        description "Full request URL.";
      }

      leaf method {
        type string;
        mandatory true;
        description "HTTP method.";
      }

      leaf description {
        type string;
        description "Human-readable test description.";
      }
    }
  }
}
