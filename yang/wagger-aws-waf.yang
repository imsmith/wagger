module wagger-aws-waf {
  namespace "urn:wagger:aws-waf";
  prefix waw;

  organization "Wagger Project";
  description "Data model for AWS WAF v2 Web ACL configuration.";

  revision 2026-04-13 {
    description "Initial revision.";
  }

  container aws-waf-config {
    description "Top-level AWS WAF v2 Web ACL configuration.";

    leaf web-acl-name {
      type string;
      mandatory true;
      description "Name of the Web ACL resource.";
    }

    leaf scope {
      type enumeration {
        enum "REGIONAL";
        enum "CLOUDFRONT";
      }
      mandatory true;
      description "Scope for the Web ACL: REGIONAL or CLOUDFRONT.";
    }

    leaf generated-at {
      type string;
      description "ISO 8601 timestamp of generation.";
    }

    list rules {
      key "name";
      description "WAF rules within the Web ACL.";

      leaf name {
        type string;
        mandatory true;
        description "Unique rule name within the Web ACL.";
      }

      leaf priority {
        type uint32;
        mandatory true;
        description "Rule evaluation priority (lower = higher priority).";
      }

      leaf rule-type {
        type enumeration {
          enum "path-allowlist";
          enum "method-enforcement";
          enum "rate-limit";
        }
        mandatory true;
        description "Logical type of this rule.";
      }

      leaf rate-limit {
        type uint32;
        description "AWS rate limit value (requests per 5-minute window).";
      }

      list path-patterns {
        key "path";
        description "Path match patterns used in the allowlist rule.";

        leaf path {
          type string;
          mandatory true;
          description "URL path or regex pattern to match.";
        }

        leaf match-type {
          type enumeration {
            enum "EXACTLY";
            enum "STARTS_WITH";
            enum "REGEX";
          }
          mandatory true;
          description "AWS WAF match type for this path pattern.";
        }
      }

      list method-groups {
        key "group-name";
        description "Method enforcement groups (one per distinct method set).";

        leaf group-name {
          type string;
          mandatory true;
          description "Identifier for this method group.";
        }

        leaf-list methods {
          type string;
          description "HTTP methods allowed for routes in this group.";
        }

        list paths {
          key "path";
          description
            "Paths belonging to this method group, as match patterns. The
             method-enforcement rule serializes each entry as a UriPath
             ByteMatchStatement (or RegexMatchStatement for parameterized
             paths) so the rule fires only on requests targeting these
             paths — without that scope the NotStatement on method would
             apply globally and block every non-matching method anywhere.";

          leaf path {
            type string;
            mandatory true;
            description "URL path, prefix, or regex for this method group.";
          }

          leaf match-type {
            type enumeration {
              enum "EXACTLY";
              enum "STARTS_WITH";
              enum "REGEX";
            }
            mandatory true;
            description "AWS WAF match type for this path pattern.";
          }
        }
      }
    }
  }
}
